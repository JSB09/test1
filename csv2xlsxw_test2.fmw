FME workspace csv2xlsxw_test2.fmw
Title: csv2xlsx

Parameters:
- SourceDataset_CSV2_5 = $(FME_MF_DIR)points-of-interest-newport-csv.csv   # Source CSV (Comma Separated Value) File(s)
- SourceDataset_CSV2 = $(FME_MF_DIR)points-of-interest-newport-csv.csv   # Source CSV (Comma Separated Value) File(s)
- DestDataset_XLSXW = $(FME_MF_DIR)ExcelOutcome\test_default_noRH.xlsx   # Destination Microsoft Excel File
- SourceDataset_CSV2_4 = $(FME_MF_DIR)points-of-interest-newport-csv.csv   # Source CSV (Comma Separated Value) File(s)
- DestDataset_XLSXW_4 = $(FME_MF_DIR)ExcelOutcome\test_FNunchecked.xlsx   # Destination Microsoft Excel File
- DestDataset_XLSXW_5 = $(FME_MF_DIR)ExcelOutcome\test_RH50.xlsx   # Destination Microsoft Excel File

Readers:
- CSV2_1: CSV2 from $(SourceDataset_CSV2)
- CSV2_2: CSV2 from $(SourceDataset_CSV2_5)
- CSV2_3: CSV2 from $(SourceDataset_CSV2_4)

Writers:
- XLSXW_1: XLSXW to $(DestDataset_XLSXW)
- XLSXW_3: XLSXW to $(DestDataset_XLSXW_4)
- XLSXW_2: XLSXW to $(DestDataset_XLSXW_5)

CSV (reader CSV2_1) [off]
    attributes: UNIQUE_REFERENCE_NUMBER uint32, NAME varchar(61), POINTX_CLASSIFICATION_CODE uint32, FEATURE_EASTING x_coordinate, FEATURE_NORTHING y_coordinate, POSITIONAL_ACCURACY_CODE uint32, UPRN uint64, TOPOGRAPHIC_TOID varchar(20), TOPOGRAPHIC_TOID_VERSION uint32, USRN uint32, USRN_MATCH_INDICATOR uint32, DISTANCE real32, ADDRESS_DETAIL varchar(59), STREET_NAME varchar(49), LOCALITY varchar(18), GEOGRAPHIC_COUNTY varchar(5), POSTCODE varchar(8), ADMINISTRATIVE_BOUNDARY varchar(19), TELEPHONE_NUMBER uint64, URL varchar(93), BRAND varchar(47), QUALIFIER_TYPE varchar(16), QUALIFIER_DATA varchar(34), PROVENANCE varchar(35), DATE_OF_SUPPLY varchar(11)
    -> Excel_noRowHeight (writer XLSXW_1)
Note: Default settings except for Row Height and/or Field Names Row Formatting
Excel_noRowHeight (writer XLSXW_1) [off]
    attributes: UNIQUE_REFERENCE_NUMBER number(20), NAME string(61), POINTX_CLASSIFICATION_CODE number(20), FEATURE_EASTING number(20), FEATURE_NORTHING number(20), POSITIONAL_ACCURACY_CODE number(20), UPRN number(20), TOPOGRAPHIC_TOID string(20), TOPOGRAPHIC_TOID_VERSION number(20), USRN number(20), USRN_MATCH_INDICATOR number(20), DISTANCE number(20), ADDRESS_DETAIL string(59), STREET_NAME string(49), LOCALITY string(18), GEOGRAPHIC_COUNTY string(5), POSTCODE string(8), ADMINISTRATIVE_BOUNDARY string(19), TELEPHONE_NUMBER number(20), URL string(93), BRAND string(47), QUALIFIER_TYPE string(16), QUALIFIER_DATA string(34), PROVENANCE string(35), DATE_OF_SUPPLY string(11)
CSV (reader CSV2_2)
    attributes: UNIQUE_REFERENCE_NUMBER uint32, NAME varchar(44), POINTX_CLASSIFICATION_CODE uint32, FEATURE_EASTING x_coordinate, FEATURE_NORTHING y_coordinate
    -> Excel_RowHeight50 (writer XLSXW_2)
Excel_RowHeight50 (writer XLSXW_2)
    attributes: UNIQUE_REFERENCE_NUMBER number(20), NAME string(44), POINTX_CLASSIFICATION_CODE number(20), FEATURE_EASTING number(20), FEATURE_NORTHING number(20)
CSV (reader CSV2_3) [off]
    attributes: UNIQUE_REFERENCE_NUMBER uint32, NAME varchar(61), POINTX_CLASSIFICATION_CODE uint32, FEATURE_EASTING x_coordinate, FEATURE_NORTHING y_coordinate, POSITIONAL_ACCURACY_CODE uint32, UPRN uint64, TOPOGRAPHIC_TOID varchar(20), TOPOGRAPHIC_TOID_VERSION uint32, USRN uint32, USRN_MATCH_INDICATOR uint32, DISTANCE real32, ADDRESS_DETAIL varchar(59), STREET_NAME varchar(49), LOCALITY varchar(18), GEOGRAPHIC_COUNTY varchar(5), POSTCODE varchar(8), ADMINISTRATIVE_BOUNDARY varchar(19), TELEPHONE_NUMBER uint64, URL varchar(93), BRAND varchar(47), QUALIFIER_TYPE varchar(16), QUALIFIER_DATA varchar(34), PROVENANCE varchar(35), DATE_OF_SUPPLY varchar(11)
    -> Excel_FNunchecked (writer XLSXW_3)
Excel_FNunchecked (writer XLSXW_3) [off]
    attributes: UNIQUE_REFERENCE_NUMBER number(20), NAME string(61), POINTX_CLASSIFICATION_CODE number(20), FEATURE_EASTING number(20), FEATURE_NORTHING number(20), POSITIONAL_ACCURACY_CODE number(20), UPRN number(20), TOPOGRAPHIC_TOID string(20), TOPOGRAPHIC_TOID_VERSION number(20), USRN number(20), USRN_MATCH_INDICATOR number(20), DISTANCE number(20), ADDRESS_DETAIL string(59), STREET_NAME string(49), LOCALITY string(18), GEOGRAPHIC_COUNTY string(5), POSTCODE string(8), ADMINISTRATIVE_BOUNDARY string(19), TELEPHONE_NUMBER number(20), URL string(93), BRAND string(47), QUALIFIER_TYPE string(16), QUALIFIER_DATA string(34), PROVENANCE string(35), DATE_OF_SUPPLY string(11)
